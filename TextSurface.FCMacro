# TextSurface.FCMacro
# 2026-05-11 18:55

from PySide import QtGui, QtCore
import FreeCADGui, FreeCAD, Draft
from statistics import mean
import os

# --- Multilang support -------------------------------------------------------

# Détermine la langue de l’utilisateur à partir de FreeCADGui
def get_user_language():
    try:
        locale = FreeCADGui.getLocale().lower()
        # Normalisation
        if locale.startswith("fr") or "french" in locale:
            return "fr"
        if locale.startswith("en") or "english" in locale:
            return "en"
        '''
        if locale.startswith("de") or "german" in locale:
            return "de"
        if locale.startswith("es") or "spanish" in locale:
            return "es"
        if locale.startswith("it") or "italian" in locale:
            return "it"
        '''
        # Fallback
        return "en"
    except Exception:
        return "en"


def tr(key):
    lang = get_user_language()
    return TRANSLATIONS.get(lang, TRANSLATIONS["en"]).get(key, key)


TRANSLATIONS = {
    "fr": {
        # Messages de sélection
        "invalid_selection_title": "Sélection invalide",
        "invalid_selection_msg": "Sélectionnez une FACE appartenant à un Body PartDesign.",

        # Fenêtre principale
        "window_title": "Réglages du texte",

        # Labels
        "label_text": "Texte :",
        "label_font": "Police :",
        "label_text_size": "Taille du texte :",
        "mirror_checkbox": "Miroir (MapReversed)",
        "label_offset_x": "Offset X :",
        "label_offset_y": "Offset Y :",
        "label_offset_z": "Offset Z :",
        "label_rotation": "Rotation (° autour de la normale) :",
        "pad_checkbox": "Pad",
        "pad_label": "Pad :",
        "cavity_checkbox": "Cavité",
        "cavity_label": "Cavité :",
        "live_preview": "Voir en temps réel",

        # Boutons
        "btn_apply": "Appliquer",
        "btn_validate": "Valider",
        "btn_cancel": "Abandon",

        # Dialogue de police
        "font_dialog_title": "Choisir une police TrueType",
        "font_dialog_filter": "Polices (*.ttf *.otf);;Tous les fichiers (*.*)",

        # Texte par défaut
        "default_text": "Text",

        # Noms d’objets dans l’arborescence
        "pad_object_name": "Pad_Texte",
        "cavity_object_name": "Cavite_Texte",
    },

    "en": {
        # Selection messages
        "invalid_selection_title": "Invalid selection",
        "invalid_selection_msg": "Select a FACE belonging to a PartDesign Body.",

        # Main window
        "window_title": "Text settings",

        # Labels
        "label_text": "Text:",
        "label_font": "Font:",
        "label_text_size": "Text size:",
        "mirror_checkbox": "Mirror (MapReversed)",
        "label_offset_x": "Offset X:",
        "label_offset_y": "Offset Y:",
        "label_offset_z": "Offset Z:",
        "label_rotation": "Rotation (° around the normal):",
        "pad_checkbox": "Pad",
        "pad_label": "Pad:",
        "cavity_checkbox": "Pocket",
        "cavity_label": "Pocket:",
        "live_preview": "Live preview",

        # Buttons
        "btn_apply": "Apply",
        "btn_validate": "OK",
        "btn_cancel": "Cancel",

        # Font dialog
        "font_dialog_title": "Choose a TrueType font",
        "font_dialog_filter": "Fonts (*.ttf *.otf);;All files (*.*)",

        # Default text
        "default_text": "Text",

        # Object names in tree
        "pad_object_name": "Pad_Text",
        "cavity_object_name": "Pocket_Text",
    }
}

# --- Déterminer le chemin du fichier INI ---
macro_fullpath = __file__
macro_path = os.path.dirname(macro_fullpath)
macro_name = os.path.splitext(os.path.basename(macro_fullpath))[0]
ini_path = os.path.join(macro_path, macro_name + ".ini")

OFFSET_INITIAL = 0.001

# --- Charger la police depuis le INI si présent ---
def loadFontFromIni(default_font):
    if os.path.exists(ini_path):
        try:
            with open(ini_path, "r", encoding="utf-8") as f:
                for line in f:
                    if line.startswith("font="):
                        font = line.split("=", 1)[1].strip()
                        if os.path.exists(font):
                            return font
        except:
            pass
    return default_font

# --- Sauvegarder la police dans le INI ---
def saveFontToIni(font_path):
    try:
        with open(ini_path, "w", encoding="utf-8") as f:
            f.write("font=" + font_path)
    except:
        pass


class TextSurfaceApp:

    def __init__(self):
        self.selObj = None
        self.nomFace = None
        self.bodyOfFace = None
        self.nouvelleShapeString = None
        self.previewObj = None
        self.FichierPoliceDeCaracteres = None
        self.dlg = None

    # ------------------------------------------------
    # Trouver le Body parent
    # ------------------------------------------------
    def findBodyOf(self, obj):
        while obj:
            if obj.TypeId == "PartDesign::Body":
                return obj
            obj = obj.getParentGeoFeatureGroup()
        return None

    # ------------------------------------------------
    # Effacer le preview global
    # ------------------------------------------------
    def clearPreview(self):
        if self.previewObj:
            try:
                FreeCAD.ActiveDocument.removeObject(self.previewObj.Name)
            except Exception:
                pass
            self.previewObj = None

    # ------------------------------------------------
    # Preview PAD
    # ------------------------------------------------
    def showPadPreview(self):
        self.clearPreview()
        doc = FreeCAD.ActiveDocument

        shape_copy = self.nouvelleShapeString.Shape.copy()

        pl_string_local = self.nouvelleShapeString.Placement
        pl_body_global = self.bodyOfFace.getGlobalPlacement()

        shape_copy.Placement = pl_body_global.multiply(pl_string_local)

        face = self.selObj.Shape.getElement(self.nomFace)
        normal_local = face.normalAt(0, 0)
        normal_global = pl_body_global.Rotation.multVec(normal_local)

        extruded = shape_copy.extrude(normal_global * self.dlg.padSpin.value())

        obj = doc.addObject("Part::Feature", "PreviewPad")
        obj.Shape = extruded
        obj.ViewObject.Transparency = 70
        obj.ViewObject.ShapeColor = (0.3, 0.8, 1.0)

        self.previewObj = obj

    # ------------------------------------------------
    # Preview CAVITÉ
    # ------------------------------------------------
    def showPocketPreview(self):
        self.clearPreview()
        doc = FreeCAD.ActiveDocument

        shape_copy = self.nouvelleShapeString.Shape.copy()

        pl_string_local = self.nouvelleShapeString.Placement
        pl_body_global = self.bodyOfFace.getGlobalPlacement()

        shape_copy.Placement = pl_body_global.multiply(pl_string_local)

        face = self.selObj.Shape.getElement(self.nomFace)
        normal_local = face.normalAt(0, 0)
        normal_global = pl_body_global.Rotation.multVec(normal_local)

        extruded = shape_copy.extrude(normal_global * (-self.dlg.cavitySpin.value()))

        obj = doc.addObject("Part::Feature", "PreviewPocket")
        obj.Shape = extruded
        obj.ViewObject.Transparency = 70
        obj.ViewObject.ShapeColor = (1.0, 0.4, 0.4)

        self.previewObj = obj

    # ------------------------------------------------
    # Correction automatique du miroir
    # ------------------------------------------------
    def autoFixMirrorDirection(self):
        face = self.selObj.Shape.getElement(self.nomFace)
        normal_face = face.normalAt(0, 0)
        normal_face.normalize()

        # Cas face horizontale
        if abs(normal_face.z) > 0.999:
            if normal_face.z < 0:
                self.nouvelleShapeString.MapReversed = True
            else:
                self.nouvelleShapeString.MapReversed = False
            return

        # Cas face non horizontale
        global_rot = self.nouvelleShapeString.getGlobalPlacement().Rotation
        normal_text = global_rot.multVec(FreeCAD.Vector(0, 0, 1))
        normal_text.normalize()

        dot = normal_text.dot(normal_face)

        if dot < 0:
            self.nouvelleShapeString.MapReversed = not self.nouvelleShapeString.MapReversed

    # ------------------------------------------------
    # Programme principal
    # ------------------------------------------------

    def applyFinalResult(self):
        doc = FreeCAD.ActiveDocument

        if self.dlg.padCheck.isChecked():
            self.autoFixMirrorDirection()
            pad = self.bodyOfFace.newObject("PartDesign::Pad", tr("pad_object_name"))
            pad.Profile = (self.nouvelleShapeString, ["Face1"])
            pad.Length = self.dlg.padSpin.value()
            pad.AllowMultiFace = False
            self.nouvelleShapeString.MapReversed = self.dlg.mirrorCheck.isChecked()
            self.nouvelleShapeString.ViewObject.Visibility = False  # ← IMPORTANT

        elif self.dlg.cavityCheck.isChecked():
            self.autoFixMirrorDirection()
            pocket = self.bodyOfFace.newObject("PartDesign::Pocket", tr("cavity_object_name"))
            pocket.Profile = self.nouvelleShapeString
            pocket.Length = self.dlg.cavitySpin.value()
            pocket.AllowMultiFace = False
            pocket.ReferenceAxis = (self.nouvelleShapeString, ["N_Axis"])
            self.nouvelleShapeString.MapReversed = self.dlg.mirrorCheck.isChecked()
            self.nouvelleShapeString.ViewObject.Visibility = False
        doc.recompute()

    def cancelOperation(self):
        FreeCAD.ActiveDocument.removeObject(self.nouvelleShapeString.Name)

    def run(self):

        # --- Déterminer la police par défaut selon OS ---
        if os.name == 'nt':
            DefaultFont = "C:/Windows/Fonts/ARIAL.TTF"
        elif os.name == 'posix':
            DefaultFont = "/usr/share/fonts/truetype/dejavu/DejaVuSans-Bold.ttf"
        else:
            DefaultFont = ""

        self.FichierPoliceDeCaracteres = loadFontFromIni(DefaultFont)

        # --- Vérification de la sélection ---
        selEx = FreeCADGui.Selection.getSelectionEx()

        invalid = (
            not selEx
            or not selEx[0].SubElementNames
            or not selEx[0].SubObjects
            or selEx[0].SubObjects[0].ShapeType != "Face"
        )

        if not invalid:
            self.selObj = selEx[0].Object
            self.bodyOfFace = self.findBodyOf(self.selObj)
            if self.bodyOfFace is None:
                invalid = True

        if invalid:
            QtGui.QMessageBox.warning(
                None,
                tr("invalid_selection_title"),
                tr("invalid_selection_msg")
            )
            return

        # --- Sélection valide ---
        self.nomFace = selEx[0].SubElementNames[0]

        TailleCaracteres = 4
        TextParDefaut = tr("default_text")

        self.nouvelleShapeString = Draft.makeShapeString(
            String=TextParDefaut,
            FontFile=self.FichierPoliceDeCaracteres,
            Size=TailleCaracteres,
            Tracking=0.0
        )

        plm = FreeCAD.Placement()
        plm.Base = FreeCAD.Vector(0, 0, 0)
        plm.Rotation.Q = (0, 0, 0, 0)

        self.nouvelleShapeString.Placement = plm
        self.nouvelleShapeString.AttachmentSupport = None

        self.bodyOfFace.addObjects([self.nouvelleShapeString])

        self.nouvelleShapeString.AttachmentOffset = FreeCAD.Placement(
            FreeCAD.Vector(0, 0, 0),
            FreeCAD.Rotation(0, 0, 0)
        )
        self.nouvelleShapeString.MapReversed = False
        self.nouvelleShapeString.AttachmentSupport = [(self.selObj, self.nomFace)]
        self.nouvelleShapeString.MapPathParameter = 0.0
        self.nouvelleShapeString.MapMode = 'InertialCS'
        self.nouvelleShapeString.Justification = u"Middle-Center"
        self.nouvelleShapeString.AttachmentOffset.Base.z = OFFSET_INITIAL

        self.nouvelleShapeString.recompute()

        # Correction miroir initiale
        self.autoFixMirrorDirection()

        # --- Ouvrir la fenêtre non-modale ---
        mainwin = FreeCADGui.getMainWindow()

        global textsurfdialog
        textsurfdialog = TextAdjustDialog(self)  # on passe l'app
        textsurfdialog.setParent(mainwin)  # ← CRUCIAL : parent = FreeCAD
        textsurfdialog.setWindowFlags(
            QtCore.Qt.Window |
            QtCore.Qt.WindowTitleHint |
            QtCore.Qt.WindowCloseButtonHint |
            QtCore.Qt.WindowMinMaxButtonsHint |
            QtCore.Qt.WindowStaysOnTopHint  # ← reste au-dessus de FreeCAD
        )
        self.dlg = textsurfdialog  # ← CRUCIAL pour preview/padSpin/etc.
        textsurfdialog.show()


class TextAdjustDialog(QtGui.QDialog):
    def __init__(self, app):
        super(TextAdjustDialog, self).__init__()
        # Rendre la fenêtre indépendante mais au-dessus de FreeCAD
        self.setWindowFlags(
            QtCore.Qt.Window |
            QtCore.Qt.WindowTitleHint |
            QtCore.Qt.WindowCloseButtonHint |
            QtCore.Qt.WindowMinMaxButtonsHint |
            QtCore.Qt.WindowStaysOnTopHint
        )

        self.app = app
        self.shape = app.nouvelleShapeString
        self.previewObj = None

        self.setWindowTitle(tr("window_title"))

        layout = QtGui.QFormLayout()

        # --- Texte ---
        self.textEdit = QtGui.QLineEdit(self.shape.String)
        self.textEdit.setMinimumWidth(300)
        layout.addRow(tr("label_text"), self.textEdit)
        self.textEdit.textChanged.connect(self.onUserChangedSomething)

        # --- Police de caractères ---
        self.fontEdit = QtGui.QLineEdit(app.FichierPoliceDeCaracteres)
        self.fontEdit.setMinimumWidth(300)
        self.fontBtn = QtGui.QPushButton(tr("btn_apply"))  # label "Choisir…" remplacé par une clé dédiée si besoin
        self.fontBtn.setText("Choisir…" if get_user_language() == "fr" else "Browse…")
        self.fontBtn.clicked.connect(self.chooseFont)

        fontLayout = QtGui.QHBoxLayout()
        fontLayout.addWidget(self.fontEdit)
        fontLayout.addWidget(self.fontBtn)
        layout.addRow(tr("label_font"), fontLayout)

        # --- Taille du texte ---
        self.sizeSpin = QtGui.QDoubleSpinBox()
        self.sizeSpin.setRange(0.1, 500)
        self.sizeSpin.setDecimals(3)
        self.sizeSpin.setSingleStep(0.5)
        self.sizeSpin.setValue(self.shape.Size)
        layout.addRow(tr("label_text_size"), self.sizeSpin)
        self.sizeSpin.valueChanged.connect(self.onUserChangedSomething)

        # --- Miroir ---
        self.mirrorCheck = QtGui.QCheckBox(tr("mirror_checkbox"))
        self.mirrorCheck.setChecked(self.shape.MapReversed)
        layout.addRow(self.mirrorCheck)
        self.mirrorCheck.toggled.connect(self.onUserChangedSomething)

        # --- Offsets ---
        self.xSpin = QtGui.QDoubleSpinBox()
        self.ySpin = QtGui.QDoubleSpinBox()
        self.zSpin = QtGui.QDoubleSpinBox()
        for spin in (self.xSpin, self.ySpin, self.zSpin):
            spin.setRange(-1000, 1000)
            spin.setDecimals(3)

        self.xSpin.setValue(self.shape.AttachmentOffset.Base.x)
        self.ySpin.setValue(self.shape.AttachmentOffset.Base.y)
        self.zSpin.setValue(self.shape.AttachmentOffset.Base.z)

        layout.addRow(tr("label_offset_x"), self.xSpin)
        layout.addRow(tr("label_offset_y"), self.ySpin)
        layout.addRow(tr("label_offset_z"), self.zSpin)

        self.xSpin.valueChanged.connect(self.onUserChangedSomething)
        self.ySpin.valueChanged.connect(self.onUserChangedSomething)
        self.zSpin.valueChanged.connect(self.onUserChangedSomething)

        # --- Rotation ---
        self.rotSpin = QtGui.QDoubleSpinBox()
        self.rotSpin.setRange(-360, 360)
        self.rotSpin.setValue(0)
        layout.addRow(tr("label_rotation"), self.rotSpin)
        self.rotSpin.valueChanged.connect(self.onUserChangedSomething)

        # --- Pad / Cavité ---
        self.padSpin = QtGui.QDoubleSpinBox()
        self.padSpin.setRange(0.1, 1000)
        self.padSpin.setDecimals(3)
        self.padSpin.setValue(1)

        self.padCheck = QtGui.QCheckBox(tr("pad_checkbox"))
        self.padCheck.toggled.connect(self.onPadToggled)

        padLayout = QtGui.QHBoxLayout()
        padLayout.addWidget(self.padSpin)
        padLayout.addWidget(self.padCheck)
        layout.addRow(tr("pad_label"), padLayout)

        self.cavitySpin = QtGui.QDoubleSpinBox()
        self.cavitySpin.setRange(0.1, 1000)
        self.cavitySpin.setDecimals(3)
        self.cavitySpin.setValue(1)

        self.cavityCheck = QtGui.QCheckBox(tr("cavity_checkbox"))
        self.cavityCheck.toggled.connect(self.onCavityToggled)

        self.padSpin.valueChanged.connect(self.onUserChangedSomething)
        self.cavitySpin.valueChanged.connect(self.onUserChangedSomething)
        self.padSpin.valueChanged.connect(self.onDepthChanged)
        self.cavitySpin.valueChanged.connect(self.onDepthChanged)

        cavityLayout = QtGui.QHBoxLayout()
        cavityLayout.addWidget(self.cavitySpin)
        cavityLayout.addWidget(self.cavityCheck)
        layout.addRow(tr("cavity_label"), cavityLayout)

        # --- Voir en temps réel ---
        self.livePreviewCheck = QtGui.QCheckBox(tr("live_preview"))
        self.livePreviewCheck.setChecked(False)
        self.livePreviewCheck.toggled.connect(self.onLivePreviewToggled)
        layout.addRow(self.livePreviewCheck)

        # --- Boutons ---
        btnLayout = QtGui.QHBoxLayout()

        applyPreviewBtn = QtGui.QPushButton(tr("btn_apply"))
        applyPreviewBtn.clicked.connect(self.updatePreview)
        btnLayout.addWidget(applyPreviewBtn)

        validateBtn = QtGui.QPushButton(tr("btn_validate"))
        validateBtn.clicked.connect(self.onAccept)
        btnLayout.addWidget(validateBtn)

        cancelBtn = QtGui.QPushButton(tr("btn_cancel"))
        cancelBtn.clicked.connect(self.onCancel)
        btnLayout.addWidget(cancelBtn)

        layout.addRow(btnLayout)

        self.setLayout(layout)

    # ------------------------------------------------
    # Acceptation
    # ------------------------------------------------

    def onCancel(self):
        # 1. Supprimer le ShapeString provisoire
        self.app.cancelOperation()

        # 2. Supprimer le PreviewPad / PreviewPocket
        self.app.clearPreview()

        # 3. Fermer la fenêtre
        self.close()

        # 4. Détruire proprement
        self.deleteLater()

    def onAccept(self):
        # 1. Appliquer les changements en cours
        self.applyChanges()

        # 2. Corriger l’offset si l’utilisateur n’a rien modifié
        if abs(self.shape.AttachmentOffset.Base.z - OFFSET_INITIAL) < 1e-6:
            self.shape.AttachmentOffset.Base.z = 0.0

        # 3. Appliquer le résultat final (Pad/Cavité)
        self.app.applyFinalResult()

        # 4. Nettoyer la preview
        self.app.clearPreview()

        # 5. Fermer la fenêtre
        self.close()

        # 6. Détruire proprement
        self.deleteLater()

    # ------------------------------------------------
    # Choix police
    # ------------------------------------------------
    def chooseFont(self):
        font_path, _ = QtGui.QFileDialog.getOpenFileName(
            self,
            tr("font_dialog_title"),
            "",
            tr("font_dialog_filter")
        )

        if font_path:
            self.fontEdit.setText(font_path)
            saveFontToIni(font_path)
            self.shape.FontFile = font_path

    # ------------------------------------------------
    # Application des changements
    # ------------------------------------------------
    def onLivePreviewToggled(self, checked):
        if checked:
            self.applyChanges(forcePreview=True)

    def applyChanges(self, forcePreview=False):

        new_text = self.textEdit.text().strip()
        if new_text:
            self.shape.String = new_text

        font_path = self.fontEdit.text().strip()
        if font_path:
            self.shape.FontFile = font_path
            saveFontToIni(font_path)

        self.shape.Size = self.sizeSpin.value()

        if self.mirrorCheck.hasFocus():
            self.shape.MapReversed = self.mirrorCheck.isChecked()

        self.shape.AttachmentOffset.Base = FreeCAD.Vector(
            self.xSpin.value(),
            self.ySpin.value(),
            self.zSpin.value()
        )

        angle = self.rotSpin.value()
        rot = FreeCAD.Rotation(FreeCAD.Vector(0, 0, 1), angle)
        self.shape.AttachmentOffset.Rotation = rot

        if not self.livePreviewCheck.isChecked() and not forcePreview:
            return

        self.shape.recompute()

        if self.padCheck.isChecked():
            self.app.showPadPreview()
        elif self.cavityCheck.isChecked():
            self.app.showPocketPreview()

    # ------------------------------------------------
    # Toggle Pad
    # ------------------------------------------------
    def onPadToggled(self, checked):
        if checked:
            self.cavityCheck.setChecked(False)
            self.applyChanges()
            if self.livePreviewCheck.isChecked():
                self.app.showPadPreview()
            else:
                self.app.clearPreview()
        else:
            self.app.clearPreview()

    # ------------------------------------------------
    # Toggle Cavité
    # ------------------------------------------------
    def onCavityToggled(self, checked):
        if checked:
            self.padCheck.setChecked(False)
            self.applyChanges()
            if self.livePreviewCheck.isChecked():
                self.app.showPocketPreview()
            else:
                self.app.clearPreview()
        else:
            self.app.clearPreview()

    # ------------------------------------------------
    # Clear preview interne (inchangé)
    # ------------------------------------------------
    def clearPreview(self):
        if not hasattr(self, "previewObj") or not self.previewObj:
            return

        obj = self.previewObj
        doc = FreeCAD.ActiveDocument

        try:
            parent = obj.getParentGeoFeatureGroup()
            if parent and parent.TypeId == "PartDesign::Body":
                parent.removeObject(obj)
            else:
                doc.removeObject(obj.Name)
        except Exception:
            pass

        self.previewObj = None

    # ------------------------------------------------
    # Preview profondeur
    # ------------------------------------------------
    def onDepthChanged(self):
        if self.livePreviewCheck.isChecked():
            if self.padCheck.isChecked():
                self.app.showPadPreview()
            elif self.cavityCheck.isChecked():
                self.app.showPocketPreview()

    # ------------------------------------------------
    # Appliquer preview
    # ------------------------------------------------
    def updatePreview(self):
        self.applyChanges(forcePreview=True)

    # ------------------------------------------------
    # Changement utilisateur
    # ------------------------------------------------
    def onUserChangedSomething(self):
        if self.livePreviewCheck.isChecked():
            self.applyChanges()


def main():
    app = TextSurfaceApp()
    app.run()


if __name__ == "__main__":
    main()
